module service-inventory {

    yang-version 1.1;
    namespace "https://www.turktelekom.com.tr/service-inventory";
    prefix srvc-inv;

    import ietf-inet-types {
        prefix inet;
    }
    import tailf-common {
        prefix tailf;
    }
    import tailf-ncs {
        prefix ncs;
    }
    import inventory {
        prefix inv;
    }

    description
      "Service inventory for multi-vendor service inventory management.";

    revision 2023-10-28 {
        description
          "Initial revision.";
    }

    typedef srvc-inv-string {
        type string {
            pattern
              '[^\s]+' {
                error-message
                  "No space/s allowed.";
            }
        }
    }

    typedef mtu-type {
        type uint16;
    }

    typedef pw-id-type {
        type uint32;
    }

    typedef pw-encapsulation-type {
        type enumeration {
            enum ethernet;
            enum vlan;
        }
    }

    typedef customer-id-type {
        type uint32 {
            range 1..2147483647;
        }
    }

    typedef sdp-id-type {
        type uint16 {
            range 1..32767;
        }
    }

    typedef l2vpn-index-type {
        type uint8 {
            range "1..24";
        }
    }

    typedef subif-id-type {
        type uint16 {
            range "2..4094";
        }
    }

    typedef encapsulation-type {
        type enumeration {
            enum dot1q-2tags;
            enum dot1q;
            enum dot1ad;
            enum e-default;
            enum untagged;
        }
    }

    typedef vlan-id-type {
        type uint16 {
            range "0..4094";
        }
        description
          "The VLAN-ID that uniquely identifies a VLAN.  This is the 12-bit
           VLAN-ID used in the VLAN Tag header.";
        reference
          "[802.1Q]";
    }

    typedef service-type {
        type enumeration {
            enum l2vpn;
            enum l3vpn;
        }
    }

    grouping commit-params-grouping {
        leaf dry-run {
            tailf:info "Display the configuration changes but do not perform the actual commit.";
            type empty;
        }
    }

    grouping elan-grouping {
        leaf name {
            tailf:info "L2VPN Service Name";
            type srvc-inv-string;
        }

        leaf mtu {
            tailf:info "Interface/service MTU";
            type mtu-type;
        }

        leaf customer-id {
            tailf:info "Provision a Customer";
            type customer-id-type;
        }

        list endpoint {
            tailf:info "L2VPN Endpoint";

            key "device";

            leaf device {
                tailf:info "PE Device";
                type leafref {
                    path "/ncs:devices/ncs:device/ncs:name";
                }
            }

            list pe-interface {
                tailf:info "PE Device Interface";

                key "id-int";

                leaf id-int {
                    tailf:info "Just a number used as index";
                    type l2vpn-index-type;
                }

                leaf if-size {
                    tailf:info "Interface Size.Ex GigabitEthernet | TenGigabitEthernet | FortyGigE | HundredGigE | Port-channel";
                    type leafref {
                        path "/inv:inventory-manager/inv:device[inv:name=current()/../../device]/inv:interface/inv:if-size";
                    }
                }

                leaf if-number {
                    when "../if-size";
                    tailf:info "Interface Size.Ex GigabitEthernet | TenGigabitEthernet | FortyGigE | HundredGigE | Port-channel";
                    type leafref {
                        path "/inv:inventory-manager/inv:device[inv:name=current()/../../device]/inv:interface[inv:if-size=current()/../if-size]/inv:if-number";
                    }
                }

                leaf subif-id {
                    tailf:info "Subinterface Id";
                    type subif-id-type;
                }

                leaf encapsulation {
                    tailf:info "Interface Encapsulation Type";
                    type encapsulation-type;
                    default "dot1q";
                }

                leaf s-vlan-id {
                    when "../encapsulation = 'dot1ad' or ../encapsulation = 'dot1q-2tags'";
                    tailf:info "Interface Encapsulation S-Vlan Id";
                    type vlan-id-type;
                }

                leaf-list c-vlan-id {
                    when "../encapsulation = 'dot1q-2tags' or ../encapsulation = 'dot1ad' or ../encapsulation = 'dot1q'";
                    tailf:info "Interface Encapsulation C-Vlan Id";
                    type union {
                        type vlan-id-type;
                        type enumeration {
                            enum "*";
                        }
                    }
                }
            }

            list neighbor {
                tailf:info "Specify The Peer To Cross Connect";

                key address;

                leaf address {
                    tailf:info "IP Address Of The Peer";
                    type inet:ip-address;
                }

                leaf pw-id {
                    tailf:info "Pseudowire Id";
                    type pw-id-type;
                }

                leaf pw-class {
                    tailf:info "PW Class Template Name To Use For This Pseudowire";
                    type string;
                }

                leaf encapsulation {
                    tailf:info "Specify Peer's Encapsulation Type";
                    type pw-encapsulation-type;
                }

                leaf sdp-id {
                    tailf:info "SDP Id";
                    type sdp-id-type;
                }
            }
        }
    }

    grouping device-service-inventory-grouping {
        leaf name {
            tailf:info "Device Name";
            type leafref {
                path "/ncs:devices/ncs:device/ncs:name";
            }
        }

        list interface {
            tailf:info "Device Physical Interface";

            key "if-size if-number";

            leaf if-size {
                tailf:info "Interface size.Ex GigabitEthernet | TenGigabitEthernet | FortyGigE | HundredGigE | Port-channel";
                type string;
            }

            leaf if-number {
                tailf:info "Interface id. Ex 0/0/0 | 0/0/0/0 | 1";
                type string;
            }

            list service {
                tailf:info "Inventory Service Type";

                key name;

                leaf name {
                    tailf:info "Service Type";
                    type service-type;
                }

                list elan {
                    when "../name = 'l2vpn'";
                    tailf:info "L2VPN Device Service Inventory";
                    key name;

                    leaf name {
                        tailf:info "L2VPN Service Name";
                        type srvc-inv-string;
                        tailf:non-strict-leafref {
                            path "/srvc-inv:service-inventory-manager/services/service/elan/name";
                        }
                    }
                }
            }
        }
    }

    grouping service-inventory-migration-grouping {
        leaf device {
            tailf:info "Device Name";
            type leafref {
                path "/ncs:devices/ncs:device/ncs:name";
            }
        }

        leaf if-size {
            tailf:info "Interface size. Ex GigabitEthernet | TenGigabitEthernet | FortyGigE | HundredGigE | Port-channel";
            type leafref {
                path "/inv:inventory-manager/inv:device[inv:name=current()/../device]/inv:interface/inv:if-size";
            }
        }

        leaf if-number {
            tailf:info "Interface id. Ex 0/0/0 | 0/0/0/0 | 1";
            type leafref {
                path "/inv:inventory-manager/inv:device[inv:name=current()/../device]/inv:interface[inv:if-size=current()/../if-size]/inv:if-number";
            }
        }
    }

    list service-inventory-manager {
        description
          "Multi-vendor service inventory management.";

        key name;
        leaf name {
            tailf:info "Service Inventory Group Name";
            type srvc-inv-string;
        }

        uses ncs:service-data;
        ncs:servicepoint service-inventory-servicepoint;

        container services {
            tailf:info "Service Inventory Manager Service Database";
            list service {
                tailf:info "Inventory Service Type";

                key name;

                leaf name {
                    tailf:info "Service Type";
                    type service-type;
                }

                list elan {
                    tailf:info "L2VPN ELAN Service Inventory";

                    key name;

                    uses srvc-inv:elan-grouping;
                }
            }
        }

        container devices {
            tailf:info "Service Inventory Manager Device Database";
            list device {
                tailf:info "Service Inventory Device";

                key name;

                uses srvc-inv:device-service-inventory-grouping;
            }
        }

        // /////////////////////////////////////////////////////////
        // Service oob-discovery action
        // /////////////////////////////////////////////////////////
        container service-discovery {
            tailf:action oob-discovery {
                tailf:actionpoint oob-discovery-point;
                input {
                    list service {
                        tailf:info "Service Id l2vpn | l3vpn";

                        key name;

                        leaf name {
                            tailf:info "Service Type";
                            type service-type;
                        }
                    }
                }
                output {
                    leaf status {
                        type string;
                    }
                }
            }
        }

        // /////////////////////////////////////////////////////////
        // Service oob-reconcile action
        // /////////////////////////////////////////////////////////
        container service-reconcile {
            tailf:action oob-reconcile {
                tailf:actionpoint oob-reconcile-point;
                input {
                    list service {
                        tailf:info "Service Id l2vpn | l3vpn";

                        key name;

                        leaf name {
                            tailf:info "Service Type";
                            type service-type;
                        }

                        list elan {
                            when "../name='l2vpn'";
                            tailf:info "L2VPN ELAN Service Inventory";

                            key name;

                            leaf name {
                                tailf:info "L2VPN ELAN Service Name";
                                type leafref {
                                    path "../../../../../srvc-inv:services/srvc-inv:service/srvc-inv:elan/srvc-inv:name";
                                }
                            }
                        }
                    }

                    uses srvc-inv:commit-params-grouping;
                }
                output {
                    leaf result {
                        type string;
                    }
                }
            }
        }

        // /////////////////////////////////////////////////////////
        // Service oob-migrate action
        // /////////////////////////////////////////////////////////
        container service-migration {
            tailf:action oob-migration {
                tailf:actionpoint oob-migration-point;

                input {

                    leaf service {
                        tailf:info "Service Type";
                        type service-type;
                    }

                    container source {
                        tailf:info "Source device information";
                        uses srvc-inv:service-inventory-migration-grouping;
                    }

                    container destination {
                        tailf:info "Destination device information";
                        uses srvc-inv:service-inventory-migration-grouping;
                    }

                    uses srvc-inv:commit-params-grouping;
                }

                output {
                    leaf result {
                        type string;
                    }
                }
            }
        }
    }
}
